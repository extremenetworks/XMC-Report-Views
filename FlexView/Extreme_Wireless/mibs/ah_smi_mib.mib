--
-- Copyright (c) 2006-2018. Aerohive Networks, Inc
-- All rights reserved.

AH-SMI-MIB DEFINITIONS ::= BEGIN

--
-- Imports
--

IMPORTS MODULE-IDENTITY, OBJECT-TYPE, enterprises
		        FROM SNMPv2-SMI 
        TEXTUAL-CONVENTION, MacAddress
		        FROM SNMPv2-TC;

--
-- Module Identity
--        

aerohive MODULE-IDENTITY
         LAST-UPDATED  "201807140000Z"  --  July 14, 2018		 
         ORGANIZATION  "Aerohive Networks, Inc"	 
         CONTACT-INFO  "info@aerohive.com		 
                        1011 McCarthy Boulevard  						
                        Milpitas, CA 95035"
         DESCRIPTION
           "This is the MIB module for object type definitions
	    that are used throughout the Aerohive Networks enterprise MIBs."

                                                                                                
         ::= { enterprises 26928 }
 

ahProduct          OBJECT IDENTIFIER ::= { aerohive 1 }

ahAP     	   OBJECT IDENTIFIER ::= { ahProduct 1 }
ahAPCommon         OBJECT IDENTIFIER ::= { ahAP 1 }
ahAPTrap	   OBJECT IDENTIFIER ::= { ahAPCommon 1 }
ahAPInterface	   OBJECT IDENTIFIER ::= { ahAPCommon 2 }
ahAPMRP            OBJECT IDENTIFIER ::= { ahAPCommon 3 }
ahAPIDP            OBJECT IDENTIFIER ::= { ahAPCommon 4 }

ahAPHiveAP020ag            OBJECT IDENTIFIER ::= { ahAP 2 }
ahAPHiveAP028ag            OBJECT IDENTIFIER ::= { ahAP 3 }
ahAPHiveAP320n           OBJECT IDENTIFIER ::= { ahAP 4 }
ahAPHiveAP340n           OBJECT IDENTIFIER ::= { ahAP 5 }
ahAPHiveAP110n           OBJECT IDENTIFIER ::= { ahAP 6 }
ahAPHiveAP120n           OBJECT IDENTIFIER ::= { ahAP 7 }
ahAPHiveAP170n           OBJECT IDENTIFIER ::= { ahAP 8 }
ahAPHiveAP330n           OBJECT IDENTIFIER ::= { ahAP 9 }
ahAPHiveAP350n           OBJECT IDENTIFIER ::= { ahAP 10 }
ahAPHiveAP121n           OBJECT IDENTIFIER ::= { ahAP 11 }
ahAPHiveAP141n           OBJECT IDENTIFIER ::= { ahAP 12 }
ahAPHiveAP370ac          OBJECT IDENTIFIER ::= { ahAP 13 }
ahAPHiveAP390ac          OBJECT IDENTIFIER ::= { ahAP 14 }
ahAPHiveAP230ac          OBJECT IDENTIFIER ::= { ahAP 15 }
ahAPHiveAP1130ac         OBJECT IDENTIFIER ::= { ahAP 16 }
ahAPHiveAP130ac          OBJECT IDENTIFIER ::= { ahAP 17 }
ahAPHiveAP250ac          OBJECT IDENTIFIER ::= { ahAP 18 }
ahAPHiveAP245Xac         OBJECT IDENTIFIER ::= { ahAP 19 }
ahAPHiveAP550ac          OBJECT IDENTIFIER ::= { ahAP 20 }
ahAPHiveAP122ac          OBJECT IDENTIFIER ::= { ahAP 21 }
ahAPHiveAP122Xac         OBJECT IDENTIFIER ::= { ahAP 22 }
ahAPHiveAP150Wac         OBJECT IDENTIFIER ::= { ahAP 23 }
ahAPHiveAP30ac           OBJECT IDENTIFIER ::= { ahAP 24 }
ahAPHiveAP630ax          OBJECT IDENTIFIER ::= { ahAP 25 }
ahAPHiveAP650ax          OBJECT IDENTIFIER ::= { ahAP 26 }
ahAPHiveAP650Xax         OBJECT IDENTIFIER ::= { ahAP 27 }

AhString ::= TEXTUAL-CONVENTION
   STATUS        current
   DESCRIPTION   "A text string with 32 octets"
   SYNTAX        OCTET STRING (SIZE (0..32))

AhNodeID ::= TEXTUAL-CONVENTION
   STATUS        current
   DESCRIPTION   "Mgmt MAC address in hex decimal notation"
   SYNTAX        MacAddress
                                      
AhInterfaceType ::= TEXTUAL-CONVENTION
   STATUS        current
   DESCRIPTION   "Interface type - (PHYSICAL, VIRTUAL)"
   SYNTAX        INTEGER {
                   ahPHYSICAL     (0), -- physical Interface
                   ahVIRTURAL    (1)  -- logical Interface
                 }

AhInterfaceMode ::= TEXTUAL-CONVENTION
   STATUS        current
   DESCRIPTION   "Interface role types"
   SYNTAX        INTEGER {
                   ahNotUsed    (0), -- interface is not used
                   ahAccess     (1), -- interface is used for access 
                   ahBackhaul   (2), -- interface is used for backhaul
                   ahBridge     (3), -- interface is used for bridge
                   ahDual       (4)  -- interface is used for dual
                   ahSensor     (5)  -- interface is used for Sensor
                   ahWLAN-Wan   (6)  -- interface is used for WLAN-Wan
                 }

AhMACProtocol ::= TEXTUAL-CONVENTION
   STATUS        current
   DESCRIPTION   "Radio Mode"
   SYNTAX        INTEGER {
                   ah11a        (0), -- 802.11a mode
                   ah11b        (1), -- 802.11b mode
                   ah11g        (2), -- 802.11g mode
                   ah11na       (3), -- 802.11na mode
                   ah11ng       (4), -- 802.11ng mode
                   ah11ac       (5), -- 802.11ac mode
                   ahBLE        (6), -- Bluetooth Low Energy mode
                   ahZigbee     (7), -- Zigbee (802.15.4) mode
                   ah11ax       (8)  -- 802.11ax mode
                 }

END
